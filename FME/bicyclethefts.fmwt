FME workspace bicyclethefts.fmwt
Title: MULTI to MULTI

Parameters:
- SourceDataset_ESRISHAPE = C:\Users\19053\OneDrive - NC\InterviewTPS\Data\Bicycle_Thefts.shp   # Source Esri Shapefile(s)
- SourceDataset_ESRISHAPE_5 = C:\Users\19053\OneDrive - NC\InterviewTPS\Data\Street furniture-Bicycle parking data.shp   # Source Esri Shapefile(s)
- DestDataset_GEODATABASE_FILE = C:\Users\19053\OneDrive - NC\InterviewTPS\BicycleThefts.gdb   # File Geodatabase
- SourceDataset_ESRISHAPE_7 = C:\Users\Vishal\OneDrive - NC\InterviewTPS\Data\Bicycle_Thefts.shp   # Source Esri Shapefile(s)
- DestDataset_CSV2 = C:\Users\19053\OneDrive - NC\InterviewTPS\tables   # Destination CSV (Comma Separated Value) Folder
- DestDataset_CSV2_9 = C:\Users\19053\OneDrive - NC\InterviewTPS\tables   # Destination CSV (Comma Separated Value) Folder
- DestDataset_GEODATABASE_FILE_5 = C:\Users\19053\OneDrive - NC\InterviewTPS\BicycleThefts.gdb   # File Geodatabase
- DestDataset_GEODATABASE_FILE_7 = C:\Users\19053\OneDrive - NC\InterviewTPS\BicycleThefts.gdb   # File Geodatabase
- DestDataset_GEODATABASE_FILE_6 = C:\Users\19053\OneDrive - NC\InterviewTPS\BicycleThefts.gdb   # File Geodatabase
- DestDataset_CSV2_7 = C:\Users\19053\OneDrive - NC\InterviewTPS\tables   # Destination CSV (Comma Separated Value) Folder
- DestDataset_CSV2_6 = C:\Users\19053\OneDrive - NC\InterviewTPS\tables   # Destination CSV (Comma Separated Value) Folder
- DestDataset_CSV2_8 = C:\Users\Vishal\OneDrive - NC\InterviewTPS\tables   # Destination CSV (Comma Separated Value) Folder

Readers:
- ESRISHAPE_1: ESRISHAPE from $(SourceDataset_ESRISHAPE)
- ESRISHAPE_2: ESRISHAPE from $(SourceDataset_ESRISHAPE_5)
- ESRISHAPE_3: ESRISHAPE from $(SourceDataset_ESRISHAPE_7)

Writers:
- GEODATABASE_FILE_1: GEODATABASE_FILE to $(DestDataset_GEODATABASE_FILE)
- CSV2_1: CSV2 to $(DestDataset_CSV2)
- CSV2_2: CSV2 to $(DestDataset_CSV2_9)
- GEODATABASE_FILE_2: GEODATABASE_FILE to $(DestDataset_GEODATABASE_FILE_5)
- GEODATABASE_FILE_3: GEODATABASE_FILE to $(DestDataset_GEODATABASE_FILE_7)
- GEODATABASE_FILE_4: GEODATABASE_FILE to $(DestDataset_GEODATABASE_FILE_6)
- CSV2_3: CSV2 to $(DestDataset_CSV2_7)
- CSV2_4: CSV2 to $(DestDataset_CSV2_6)
- CSV2_5: CSV2 to $(DestDataset_CSV2_8)

Bicycle_Thefts (reader ESRISHAPE_3)
    attributes: Index_ char(80), event_uniq char(80), Primary_Of char(80), Occurrence char(80), Occurren_1 long, Occurren_2 long, Occurren_3 long, Occurren_4 char(80), Division long, City char(80), Location_T char(80), premisetyp char(80), Bike_Make char(80), Bike_Model char(80), Bike_Type char(80), Bike_Speed long, Bike_Colou char(80), Cost_of_Bi char(80), Status char(80), Hood_ID char(80), Neighbourh char(80), Lat double, Long double, ObjectId long
    -> AttributeRenamer
Note: Filtering data based on top 5 offenses.
Note: Filtering data of each year to analyze the trend.
Note: Thefts of Bicycles below $500, $500 to $1000, and above 500$
Note: Thefts within and outside 10 meters of bicycle parking.
AttributeRenamer
    ATTR_TABLE:
      RENAME_SET_DEFAULT Occurren_1 > Year
      RENAME_SET_DEFAULT Occurren_2 > Month
      RENAME_SET_DEFAULT _count > Thefts
    -> StatisticsCalculator_2
    -> StatisticsCalculator
    -> Tester
    -> StatisticsCalculator_6
    -> Tester_6
    -> Tester_5
    -> Tester_4
    -> Tester_7
    -> Tester_8
    -> Tester_9
    -> Tester_10
    -> Tester_13
    -> Tester_12
    -> Tester_11
    -> StatisticsCalculator_9
    -> StatisticsCalculator_10
    -> StatisticsCalculator_11

Bookmark: CostBasedAnalysis
Tester
    BOOL_OP = OR
    TEST_CLAUSE = TEST @Value(Cost_of_Bi) > 500
    TEST_MODE = TEST
    PASSED -> Tester_2
    FAILED -> StatisticsCalculator_4
    FAILED -> TheftsBelow500 (writer GEODATABASE_FILE_4)
Tester_2
    BOOL_OP = OR
    TEST_CLAUSE = TEST @Value(Cost_of_Bi) > 1000
    TEST_MODE = TEST
    PASSED -> StatisticsCalculator_5
    PASSED -> TheftsAbove1000 (writer GEODATABASE_FILE_4)
    FAILED -> StatisticsCalculator_3
    FAILED -> Thefts500_1000 (writer GEODATABASE_FILE_4)
StatisticsCalculator_5
    COMPUTE_HISTOGRAM = NO
    COUNT_ATTR = Above_1000
    PREPEND_ATTR_NAME_CHOICE = For multiple results only
    STATS_ATTRS = Cost_of_Bi
    SUMMARY -> CostofBicycle (writer CSV2_2)
TheftsAbove1000 (writer GEODATABASE_FILE_4)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer
Thefts500_1000 (writer GEODATABASE_FILE_4)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer
StatisticsCalculator_3
    COMPUTE_HISTOGRAM = NO
    COUNT_ATTR = 500_1000
    PREPEND_ATTR_NAME_CHOICE = For multiple results only
    STATS_ATTRS = Cost_of_Bi
    SUMMARY -> CostofBicycle (writer CSV2_2)
StatisticsCalculator_4
    COMPUTE_HISTOGRAM = NO
    COUNT_ATTR = Below_500
    PREPEND_ATTR_NAME_CHOICE = For multiple results only
    STATS_ATTRS = Cost_of_Bi
    SUMMARY -> CostofBicycle (writer CSV2_2)
CostofBicycle (writer CSV2_2)
    attributes: Below_500 string, 500_1000 string, Above_1000 string
TheftsBelow500 (writer GEODATABASE_FILE_4)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer

Bookmark: Statistical
StatisticsCalculator_6
    COMPUTE_HISTOGRAM = NO
    COUNT_ATTR = _count
    GROUP_BY = Primary_Of
    PREPEND_ATTR_NAME_CHOICE = For multiple results only
    STATS_ATTRS = Primary_Of
    SUMMARY -> Sorter
Sorter
    SORT_PARM = _count NUMERIC DESCENDING
    SORTED -> Counter
Counter
    CNT_ATTR = ID
    DOMAIN = counter
    SCOPE = Global
    START = 1
    -> Tester_3
Tester_3
    BOOL_OP = OR
    TEST_CLAUSE:
      TEST @Value(ID) = 1
      TEST @Value(ID) = 2
      TEST @Value(ID) = 3
      TEST @Value(ID) = 4
      TEST @Value(ID) = 5
    TEST_MODE = TEST
    PASSED -> PrimaryOffence (writer CSV2_1)
Note: Statisticsal Analysis - Offenses
PrimaryOffence (writer CSV2_1)
    attributes: Primary_Of string, _count string, ID string
StatisticsCalculator
    COMPUTE_HISTOGRAM = NO
    COUNT_ATTR = _count
    GROUP_BY = Year
    PREPEND_ATTR_NAME_CHOICE = For multiple results only
    STATS_ATTRS = Year
    SUMMARY -> Year (writer CSV2_1)
Note: Statisticsal Analysis - Yearly
Year (writer CSV2_1)
    attributes: Year string, _count string
StatisticsCalculator_2
    COMPUTE_HISTOGRAM = NO
    COUNT_ATTR = _count
    GROUP_BY = Month Year
    PREPEND_ATTR_NAME_CHOICE = For multiple results only
    STATS_ATTRS = Month
    SUMMARY -> AttributeManager
AttributeManager
    ATTR_TABLE = SET_TO Month = FME_CONDITIONAL:DEFAULT_VALUE'_FME_NO_OP_'BOOL_OP;OR;COMPOSITE_TEST;<Unused>;TEST @Value(Month) = 1'January'BOOL_OP;OR;COMPOSITE_TEST;<Unused>;TEST @Value(Month) = 2'February'BOOL_OP;OR;COMPOSITE_TEST;<Unused>;TEST @Value(Month) = 3'March'BOOL_OP;OR;COMPOSITE_TEST;<Unused>;TEST @Value(Month) = 4'April'BOOL_OP;OR;COMPOSITE_TEST;<Unused>;TEST @Value(Month) = 5'May'BOOL_OP;OR;COMPOSITE_TEST;<Unused>;TEST @Value(Month) = 6'June'BOOL_OP;OR;COMPOSITE_TEST;<Unused>;TEST @Value(Month) = 7'July'BOOL_OP;OR;COMPOSITE_TEST;<Unused>;TEST @Value(Month) = 8'August'BOOL_OP;OR;COMPOSITE_TEST;<Unused>;TEST @Value(Month) = 9'September'BOOL_OP;OR;COMPOSITE_TEST;<Unused>;TEST @Value(Month) = 10'October'BOOL_OP;OR;COMPOSITE_TEST;<Unused>;TEST @Value(Month) = 11'November'BOOL_OP;OR;COMPOSITE_TEST;<Unused>;TEST @Value(Month) = 12'December'FME_NUM_CONDITIONS13___
    -> Month (writer CSV2_1)
Note: Statisticsal Analysis - Monthly
Month (writer CSV2_1)
    attributes: _count string, Year string, Month string
StatisticsCalculator_9
    COMPUTE_HISTOGRAM = NO
    COUNT_ATTR = _count
    GROUP_BY = Location_T
    PREPEND_ATTR_NAME_CHOICE = For multiple results only
    STATS_ATTRS = Location_T
    SUMMARY -> Sorter_2
Sorter_2
    SORT_PARM = _count NUMERIC DESCENDING
    SORTED -> Counter_2
Counter_2
    CNT_ATTR = id
    DOMAIN = counter
    SCOPE = Global
    START = 1
    -> Tester_14
Tester_14
    BOOL_OP = OR
    TEST_CLAUSE = TEST @Value(id) <= 10
    TEST_MODE = TEST
    PASSED -> Location (writer CSV2_5)
Location (writer CSV2_5)
    attributes: Location_T string, _count string, id string
StatisticsCalculator_10
    COMPUTE_HISTOGRAM = NO
    GROUP_BY = Year
    PREPEND_ATTR_NAME_CHOICE = For multiple results only
    STATS_ATTRS = Cost_of_Bi
    SUM_ATTR = _sum
    SUMMARY -> TotalLoss (writer CSV2_5)
TotalLoss (writer CSV2_5)
    attributes: Year string, _sum string
StatisticsCalculator_11
    COMPUTE_HISTOGRAM = NO
    GROUP_BY = Status
    PREPEND_ATTR_NAME_CHOICE = For multiple results only
    STATS_ATTRS = Cost_of_Bi
    SUM_ATTR = _sum
    SUMMARY -> TheftStatus (writer CSV2_5)
TheftStatus (writer CSV2_5)
    attributes: Status string, _sum string

Bookmark: Top 5 Offense
Tester_8
    BOOL_OP = OR
    TEST_CLAUSE = CASE_INSENSITIVE_TEST @Value(Primary_Of) = THEFT UNDER
    TEST_MODE = TEST
    PASSED -> TheftUnder (writer GEODATABASE_FILE_2)
TheftUnder (writer GEODATABASE_FILE_2)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer
Tester_7
    BOOL_OP = OR
    TEST_CLAUSE = CASE_INSENSITIVE_TEST @Value(Primary_Of) = THEFT UNDER - BICYCLE
    TEST_MODE = TEST
    PASSED -> TheftUnderBicycle (writer GEODATABASE_FILE_2)
TheftUnderBicycle (writer GEODATABASE_FILE_2)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer
Tester_4
    BOOL_OP = OR
    TEST_CLAUSE = CASE_INSENSITIVE_TEST @Value(Primary_Of) = B&E
    TEST_MODE = TEST
    PASSED -> BreakingEntering (writer GEODATABASE_FILE_2)
BreakingEntering (writer GEODATABASE_FILE_2)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer
Tester_5
    BOOL_OP = OR
    TEST_CLAUSE = CASE_INSENSITIVE_TEST @Value(Primary_Of) = THEFT OF EBIKE UNDER $5000
    TEST_MODE = TEST
    PASSED -> TheftOfBikeUnder5000 (writer GEODATABASE_FILE_2)
TheftOfBikeUnder5000 (writer GEODATABASE_FILE_2)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer
Tester_6
    BOOL_OP = OR
    TEST_CLAUSE = CASE_INSENSITIVE_TEST @Value(Primary_Of) = PROPERTY - FOUND
    TEST_MODE = TEST
    PASSED -> PropertyFound (writer GEODATABASE_FILE_2)
PropertyFound (writer GEODATABASE_FILE_2)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer

Bookmark: YearlyAnalysis
Tester_9
    BOOL_OP = OR
    TEST_CLAUSE = TEST @Value(Year) = 2014
    TEST_MODE = TEST
    PASSED -> Year2014 (writer GEODATABASE_FILE_2)
Year2014 (writer GEODATABASE_FILE_2)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer
Tester_10
    BOOL_OP = OR
    TEST_CLAUSE = TEST @Value(Year) = 2015
    TEST_MODE = TEST
    PASSED -> Year2015 (writer GEODATABASE_FILE_2)
Year2015 (writer GEODATABASE_FILE_2)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer
Tester_11
    BOOL_OP = OR
    TEST_CLAUSE = TEST @Value(Year) = 2016
    TEST_MODE = TEST
    PASSED -> Year2016 (writer GEODATABASE_FILE_2)
Year2016 (writer GEODATABASE_FILE_2)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer
Tester_12
    BOOL_OP = OR
    TEST_CLAUSE = TEST @Value(Year) = 2017
    TEST_MODE = TEST
    PASSED -> Year2017 (writer GEODATABASE_FILE_2)
Year2017 (writer GEODATABASE_FILE_2)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer
Tester_13
    BOOL_OP = OR
    TEST_CLAUSE = TEST @Value(Year) = 2018
    TEST_MODE = TEST
    PASSED -> Year2018 (writer GEODATABASE_FILE_2)
Year2018 (writer GEODATABASE_FILE_2)
    attributes: Year char(200), Month char(200), Index_ char(80), event_uniq char(80), Primary_Of char(80), Occurrence char(80), Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer

Bookmark: StreetFurnitureAnalysis
Street furniture-Bicycle parking data (reader ESRISHAPE_2)
    attributes: FIELD_1 number(18,0), FIELD_2 number(18,0), FIELD_3 char(80), FIELD_4 char(80), FIELD_5 char(80), FIELD_6 char(80), FIELD_7 char(80), FIELD_8 char(80), FIELD_9 char(80), FIELD_10 double, FIELD_11 number(18,0), FIELD_12 char(80), FIELD_13 char(80), FIELD_14 char(80), FIELD_15 number(18,0), FIELD_16 double, FIELD_17 double, FIELD_18 double, FIELD_19 double
    -> GeographicBufferer
GeographicBufferer
    ANGLE = 22.5
    BufferDist = 10
    BufferUnit = Meters
    CAP_STYLE = Round
    CORNER_STYLE = Round
    MITER_LIMIT = 1
    -> Clipper [CLIPPER]
Bicycle_Thefts (reader ESRISHAPE_1)
    attributes: Index_ char(80), event_uniq char(80), Primary_Of char(80), Occurrence char(80), Occurren_1 long, Occurren_2 long, Occurren_3 long, Occurren_4 char(80), Division long, City char(80), Location_T char(80), premisetyp char(80), Bike_Make char(80), Bike_Model char(80), Bike_Type char(80), Bike_Speed long, Bike_Colou char(80), Cost_of_Bi char(80), Status char(80), Hood_ID char(80), Neighbourh char(80), Lat double, Long double, ObjectId long
    -> Clipper [CLIPPEE]
Clipper
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> Within10m (writer GEODATABASE_FILE_1)
    INSIDE -> StatisticsCalculator_7
    OUTSIDE -> Outside10m (writer GEODATABASE_FILE_3)
    OUTSIDE -> StatisticsCalculator_8
Within10m (writer GEODATABASE_FILE_1)
    attributes: Index_ char(80), event_uniq char(80), Primary_Of char(80), Occurrence char(80), Occurren_1 integer, Occurren_2 integer, Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer, _clipped char(200)
StatisticsCalculator_7
    COMPUTE_HISTOGRAM = NO
    COUNT_ATTR = _count
    PREPEND_ATTR_NAME_CHOICE = For multiple results only
    STATS_ATTRS = _clipped
    SUMMARY -> ParkingThefts (writer CSV2_4)
StatisticsCalculator_8
    COMPUTE_HISTOGRAM = NO
    COUNT_ATTR = _count
    PREPEND_ATTR_NAME_CHOICE = For multiple results only
    STATS_ATTRS = _clipped
    SUMMARY -> ParkingThefts (writer CSV2_4)
ParkingThefts (writer CSV2_4)
    attributes: _count string
Outside10m (writer GEODATABASE_FILE_3)
    attributes: Index_ char(80), event_uniq char(80), Primary_Of char(80), Occurrence char(80), Occurren_1 integer, Occurren_2 integer, Occurren_3 integer, Occurren_4 char(80), Division integer, City char(80), Location_T char(80), premisetyp char(80), Bike_Make char(80), Bike_Model char(80), Bike_Type char(80), Bike_Speed integer, Bike_Colou char(80), Cost_of_Bi char(80), Status char(80), Hood_ID char(80), Neighbourh char(80), Lat double, Long double, ObjectId integer
